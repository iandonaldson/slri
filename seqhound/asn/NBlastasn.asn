-- $Id: NBlastasn.asn,v 1.1.1.1 2001/10/11 17:37:13 gbader Exp $
-- ***************************************************************************
--
--  NBlast Data Specification
--
--  NBlast-Result and NBlast-GiandEval and their respective sets
--
--  Author: Michel Dumontier        micheld@mshri.on.ca  
--             
--  Publication to cite:
--
--  Hogue Lab - University of Toronto Biochemistry Department and the
--  Samuel Lunenfeld Research Institute, Mount Sinai Hospital
--  http://bioinfo.mshri.on.ca  hogue@mshri.on.ca
--
--  REVISIONS
--  April 2, 2001  
--
-- 
--  NOTE:  This specification is in a variant of ASN.1 1990 that may not
--         be compatible with newer ASN.1 tools.  This specification also
--         depends on public domain specifications available from the
--         U.S. National Center for Biotechnology Information (NCBI)
--         ftp://ncbi.nlm.nih.gov/toolbox/ncbi_tools/
--         http://www.ncbi.nlm.nih.gov/Toolbox/
--
--
--  Copyright Notice:
--
--  Copyright ©2001 Mount Sinai Hospital (MSH)
--
--  This program is free software; you can redistribute it and/or 
--  modify it under the terms of the GNU General Public License as 
--  published by the Free Software Foundation; either version 2 of 
--  the License, or any later version.
--
--  This program is distributed in the hope that it will be useful, 
--  but WITHOUT ANY WARRANTY; without even the implied warranty of 
--  MERCHANTABILITY or FITNESS FOR A PARTICULAR PURPOSE. 
--
--  See the GNU General Public License for more details.
--
--  You should have received a copy of the GNU General Public License 
--  along with this program; if not, write to the
--         Free Software Foundation, Inc., 
--         59 Temple Place, Suite 330, Boston, MA  
--         02111-1307  USA 
--  or visit http://www.gnu.org/copyleft/gpl.html
--
--  SPECIAL EXCEPTIONS
--
--  As a special exception, Mount Sinai Hospital gives permission to 
--  link this program with the following non-GPL programs or libraries, 
--  and distribute the resulting executable, without including the source 
--  code for these in the source distribution:
--
--  a) CodeBase 6.5 or greater from Sequiter Software Inc.
--
--  b) The C or C++ interface to Oracle 8.x or greater, from
--     Oracle Corporation or IBM DB2 UDB.
--
-- ***************************************************************************


NBlast DEFINITIONS ::=
BEGIN

EXPORTS NBlast-Result-Set, NBlast-Result, NBlast-Scores, NBlast-GiAndEval, NBlast-GiAndEval-set;


-- The NBlast-Result stores the useful parts of a seqalign from Blast
-- Including the alignment and bitscore from which the evalue and pvalue
-- can later be regenerated, if necessary
NBlast-Result ::= SEQUENCE {
	numseg INTEGER ,
	starts SEQUENCE OF INTEGER ,
	lens SEQUENCE OF INTEGER ,
	scores SEQUENCE OF NBlast-Scores }

NBlast-Scores ::= SEQUENCE {
	bitscore REAL ,
	evalue REAL }

NBlast-Result-Set ::= SEQUENCE {
	query-gi INTEGER OPTIONAL ,
	subject-gi INTEGER OPTIONAL ,
	results SEQUENCE OF NBlast-Result }


-- The NBlast-GiAndEval stores the gi and the associated evalue for a neighbour
-- The NBlast-GiAndEval set data specification is used to store all neighbours for a gi
-- in the NBlastDB
NBlast-GiAndEval ::= SEQUENCE {
	subject-gi INTEGER ,
	evalue REAL }

NBlast-GiAndEval-set ::= SEQUENCE {
	query-gi INTEGER OPTIONAL ,
	giandevals SEQUENCE OF NBlast-GiAndEval }

END
